module radio-bridge-tg-logging {

    yang-version "1.1";

    // namespace
    namespace "http://siklu.com/yang/tg/logging";

    prefix "rb-tg-log";

    import radio-bridge-tg-types {
        prefix rb-tg-types;
    }
    
    // meta
    organization
      "Siklu";

    contact
      "Support: <https://siklu.com/contact/>";

    description
      "TODO";

    revision 2025-02-06 {
        description
          "Added rpc add-debug-log to receiving test information for debug";
        reference
          "";
    }

    revision 2024-02-16 {
        description
          "Added rpc set-log-config to configuring module loggin severity";
        reference
          "";
    }

    revision 2023-10-11 {
        description
          "Change name the rpc for printing internal entity to debug-dump-class-info-into-log.
           Change name of the parameter to class-name";
        reference
          "";
    }

    revision 2023-10-10 {
        description
          "Add rpc for printing internal entity (e.g, class) db for debug";
        reference
          "";
    }
      
    revision 2023-07-06 {
        description
          "increase log-module-type string length to 256";
        reference
          "";
    }
    
    revision 2023-04-20 {
        description
          "Change yang version to 1.1";
        reference
          "";
    }

    revision 2021-12-29 {
        description
          "Initial revision";
        reference
          "TBD";
    }

    // extension statements
    // feature statements
    // identity statements
    // typedef statements  
    typedef log-severity-type {
        type enumeration {
            enum None {
                description
                  "Logging is disabled";
            }
            enum Error {
                description
                  "Error level severity";
            }
            enum Warning {
                description
                  "Warning level severity";
            }
            enum Info {
                description
                  "Information level severity";
            }
            enum Verbose {
                description
                  "Verbose level severity";
            }
        }
        description
          "All possible severity levels for logging";
    }

    typedef log-module-type {
        type union {
            type enumeration {
                enum radio-firmware {
                    description
                      "Logs generated by radio firmware";
                }
            }
            type string {
                length 1..256;
            }
        }
        description
          "All modules allowed for log configuration";
    }

    typedef tech-file-creation-state-type {
        type enumeration {
            enum idle {
                description
                  "Ready to create a technician file";
            }
            enum in-progress {
                description
                  "Currently creating a technician file";
            }
            enum failure {
                description
                  "An error was encountered in the last technician file creation attempt. idle state.";
            }
        }
        description
          "Possible states in the technician file creation process";
    }

    // grouping statements
    grouping logging-config-top {
        list log {
            leaf "module" {
                type log-module-type;
                description
                  "Log module type";
            }
            key "module";
            leaf severity {
                type log-severity-type;
                description
                  "Module log severity";
            }
            description
              "List of all configurable log modules";
        }
        description
          "Grouping for logs configuration";
    }

    grouping logging-state-top {
        leaf technician-file-creation {
            type tech-file-creation-state-type;
            default idle;
            description
              "The technician file creation process state";
        }
        description
          "Grouping for logs state";
    }
// data definition statements
// augment statements

// rpc statements
rpc debug-dump-class-info-into-log {
    description
      "RPC for printing a specific class internal db information into clixon log. Used for debug.
      Example: debug dump-class-info-into-log class-name ClockInfoProtocol";
    input{
        leaf class-name {
            type rb-tg-types:radio-bridge-tg-string {
                length "1..128";
            }
            mandatory true;
            description
              "Name of class to print its internal db info (e.g, ClockInfoProtocol)";
        }
    }
}

rpc debug-set-log-config {
    description
      "RPC for configuring log module severity. Used for temporal configuring.
      Example: debug set-log-config module-name radio-firmware severity Verbose";
    input{
        leaf module-name {
            type log-module-type;
            mandatory true;
            description
              "Name of module for configuring (e.g. radio-firmware) ";
        }
        leaf severity  {
            type log-severity-type;
            mandatory true;
            description
              "Module log severity (e.g. None, Verbose, Info)";
        }
    }
}

rpc add-debug-log {
    description
      "This RPC is dedicated for printing information for debug";
    input{
        leaf title {
            type string {
                length "1..256";
            }
            mandatory true;
            description
              "Title of the test";
        }
        leaf content {
            type string {
                length "1..1024";
            }
            description
              "Content or description of the test";
        }
    }
}

// notification statements
}
